module acme-system {
  namespace "http://acme.example.com/system";
  prefix "acme";

  organization "ACME Systems, Inc.";
  description
    "Example YANG module for a system configuration.";

  revision 2007-11-05 {
    description "Initial version.";
  }

  container system {
    leaf host-name {
      type string;
      description "Hostname for this system.";
    }

    leaf-list domain-search {
      type string;
      description "List of domain names to search.";
    }

    container login {
      leaf message {
        type string;
        description "Message given at start of login session.";
      }

      list user {
        key "name";

        leaf name {
          type string;
        }

        leaf full-name {
          type string;
        }

        leaf class {
          type string;
        }
      }
    }
  }
}
